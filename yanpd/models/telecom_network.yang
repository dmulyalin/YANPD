module device {

	list nodes {
		list router-base {
			leaf-list labels;
			leaf uuid;
			leaf hostname;		
		}
	}

	list links {
	
		list vendor {
			source router-base;
			target vendor;
			list properties {
				leaf contract;
			}
		}
		
		list hardware {
			source router-base;
			target hardware;
			list properties {
				leaf pid;
			}
		}
	
	}
}
